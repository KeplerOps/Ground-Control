[[SECTION]]
TITLE: Wave 1 — Foundation

[TEXT]
This section describes the foundational requirements for end-to-end testing.

[REQUIREMENT]
UID: E2E-REQ-001
TITLE: Foundation requirement
STATEMENT: >>>
Root requirement for end-to-end testing.
<<<
COMMENT: GitHub issues: #10

[REQUIREMENT]
UID: E2E-REQ-002
TITLE: Child of foundation
STATEMENT: >>>
Direct child of the foundation requirement.
<<<
COMMENT: GitHub issues: #11
RELATIONS:
- TYPE: Parent
  VALUE: E2E-REQ-001

[REQUIREMENT]
UID: E2E-REQ-003
TITLE: Grandchild requirement
STATEMENT: >>>
Grandchild requirement with two issue references.
<<<
COMMENT: GitHub issues: #12 #13
RELATIONS:
- TYPE: Parent
  VALUE: E2E-REQ-002

[[/SECTION]]

[[SECTION]]
TITLE: Wave 2 — Integration

[REQUIREMENT]
UID: E2E-REQ-004
TITLE: Integration requirement
STATEMENT: >>>
Standalone integration requirement with one issue reference.
<<<
COMMENT: GitHub issues: #14

[TEXT]
Orphan requirements are intentionally left without relations for testing.

[REQUIREMENT]
UID: E2E-REQ-005
TITLE: Orphan requirement
STATEMENT: >>>
Intentional orphan — no relations and no issue references.
<<<

[[/SECTION]]

[DOCUMENT]
TITLE: Ground Control — Infrastructure Requirements
UID: GC-INFRA

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: TITLE
    TYPE: String
    REQUIRED: True
  - TITLE: STATEMENT
    TYPE: String
    REQUIRED: True
  - TITLE: COMMENT
    TYPE: String
    REQUIRED: False
  RELATIONS:
  - TYPE: Parent
  - TYPE: File

[TEXT]
STATEMENT: >>>
Infrastructure requirements for Ground Control. Covers cloud database,
infrastructure as code, networking, secrets management, and developer
workflow. These requirements support the transition from local Docker
development to cloud-hosted services while preserving local development
as a fallback.
<<<

[[SECTION]]
TITLE: Cloud Database

[REQUIREMENT]
UID: INFRA-RDS
TITLE: Cloud PostgreSQL database
STATEMENT: >>>
Provision an RDS PostgreSQL 16 instance in AWS account catalyst-dev
(516608939870), region us-east-2. The instance must be publicly accessible
with security controls (security group + TLS). Use the smallest viable
instance class for pre-alpha single-user workload (db.t4g.micro, 20 GiB gp3).

Apache AGE is not available on RDS and is not required — all graph analysis
works via JPA (ADR-005 documents this trade-off). Redis is not used and is
not required.
<<<
COMMENT: See ADR-015, ADR-002, ADR-005

[REQUIREMENT]
UID: INFRA-RDS-BACKUP
TITLE: Database backup and retention
RELATIONS:
- TYPE: Parent
  VALUE: INFRA-RDS
STATEMENT: >>>
Automated backups with a minimum 7-day retention period. Deletion protection
enabled on the RDS instance. A final snapshot is required before any instance
deletion.
<<<

[REQUIREMENT]
UID: INFRA-RDS-NETWORK
TITLE: Database network security
RELATIONS:
- TYPE: Parent
  VALUE: INFRA-RDS
STATEMENT: >>>
Security group restricting inbound access to the developer's current IP
address on the PostgreSQL port (5432/tcp). A mechanism (Makefile target or
script) must exist to update the allowed IP when it changes.
<<<

[REQUIREMENT]
UID: INFRA-RDS-CREDS
TITLE: Database credential management
RELATIONS:
- TYPE: Parent
  VALUE: INFRA-RDS-NETWORK
STATEMENT: >>>
Database credentials must be generated automatically (random password), never
stored in plaintext in source control or Terraform variable files. Credentials
must be stored in a managed secrets service (AWS SSM Parameter Store
SecureString). Credentials must be retrievable via AWS CLI for local
development use.
<<<

[REQUIREMENT]
UID: INFRA-RDS-ENCRYPT
TITLE: Database encryption
RELATIONS:
- TYPE: Parent
  VALUE: INFRA-RDS-NETWORK
STATEMENT: >>>
Encryption at rest via RDS storage encryption (AES-256, AWS-managed key).
Encryption in transit via TLS required for all database connections
(sslmode=require minimum in connection strings, rds.force_ssl=1 parameter).
<<<

[REQUIREMENT]
UID: INFRA-DATA-MIGRATE
TITLE: Data migration
RELATIONS:
- TYPE: Parent
  VALUE: INFRA-RDS
STATEMENT: >>>
A documented path to migrate existing local Docker PostgreSQL data to cloud
RDS. Migration must preserve UUIDs, audit trail (Envers revinfo and _audit
tables), and traceability links. Flyway migrations must run cleanly on a
fresh RDS instance, including V010 AGE graceful fallback (AGE extension not
available, EXCEPTION handler skips graph setup).
<<<

[[SECTION]]
TITLE: Infrastructure as Code

[REQUIREMENT]
UID: INFRA-IAC
TITLE: Infrastructure as code
STATEMENT: >>>
All cloud resources must be defined in Terraform. No manual AWS Console
resource creation except for the one-time bootstrap of the Terraform state
backend (S3 bucket + DynamoDB table).
<<<

[REQUIREMENT]
UID: INFRA-TFSTATE
TITLE: Terraform state backend
RELATIONS:
- TYPE: Parent
  VALUE: INFRA-IAC
STATEMENT: >>>
S3 bucket and DynamoDB table for Terraform remote state storage and locking.
The bucket must have versioning enabled, server-side encryption (AES-256),
and public access blocked (all four S3 public access block settings enabled).
<<<

[REQUIREMENT]
UID: INFRA-TF-MODULES
TITLE: Modular Terraform structure
RELATIONS:
- TYPE: Parent
  VALUE: INFRA-IAC
STATEMENT: >>>
Reusable Terraform modules for networking (VPC/security groups), database
(RDS), and secrets (SSM parameters). Environment-specific wiring in
environments/dev/ directory. Module inputs and outputs documented.
<<<

[[SECTION]]
TITLE: Developer Workflow

[REQUIREMENT]
UID: INFRA-DEV-WORKFLOW
TITLE: Local development workflow
STATEMENT: >>>
Makefile targets for: retrieving cloud DB credentials from SSM
(cloud-db-env), starting the application with cloud DB configuration
(dev-cloud), and updating the security group with the developer's current
IP address (cloud-db-ip). The existing local Docker Compose workflow must
be preserved as a fallback for offline development.
<<<
